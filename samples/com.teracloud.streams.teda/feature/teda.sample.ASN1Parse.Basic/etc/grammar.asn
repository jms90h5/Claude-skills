MyModule DEFINITIONS IMPLICIT TAGS ::= 
BEGIN

Sample ::= SEQUENCE
{
	orders [0] SEQUENCE OF Order OPTIONAL,
	...
}

Order ::= SEQUENCE
{
	size    [0] PaperSize DEFAULT "a4",
	count   [1] INTEGER (0..100) DEFAULT 1,
	color   [2] Color DEFAULT "white",
	ordered [3] GeneralizedTime,
	...
}

PaperSize ::= ENUMERATED
{
	a0 (0),
	a1 (1),
	a2 (2),
	a3 (3),
	a4 (4),
	a5 (5)
} 

Color ::= ENUMERATED
{
	black (0),
	white (1),
	red (2),
	green (3),
	yellow (4)
}

END
